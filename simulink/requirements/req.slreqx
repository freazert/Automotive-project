# req

## SE_001: Maintain speed
The controller needs to be able to maintain a constant speed between 40 and 180 kmph

## SE_002: Set desired speed
The driver needs the possibility to set the desired speed between 40 and 180 kmph.

### SE_002_01: PID control -plant assumptions
The pid controller needs to be adapted to maintain a constant speed for a car with following assumptions:
- mass = 100kg
- friction constant = 50Nsec/m

### SE_002_02: PID control - setting time
The setting time of the controller needs to be less or equal to 10 seconds where the desired speed is within the absolute tolerance of +- 0.5kmph. The targeted settling time under the assumption of controlling with a delta speed of maximum 20kmph.

## S3_003: Maintain speed on slope
Bij een hoek van >20° & <20° mag de snelheid maar 5 km/uur afwijken
