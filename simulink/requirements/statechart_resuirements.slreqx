# statechart_resuirements

## ST_01: Activate
Start CC

### ST_01_01: Set required speed

### ST_01_02: Deactivate
Stop CC

### ST_04_01: Reduce speed with break
Break -> CC suspended

#### ST_04_02: Resume CC after break
Reactivate CC

#### ST_04_03: Deactivate CC after break
Deactivate CC

### ST_05_01: Suspend CC when transmission is out of top gear
Shift out of top gear

#### ST_05_02: Resume CC when transmission is back in top gear
Reactivate CC

#### ST_05_03: Deactive CC after transmission when out of top gear
Deactivate CC

### ST_06: Maintain speed

## ST_02: Show speed
Show Driving speed

## ST_03_01: Accelerate with pedal
Driver may go faster

### ST_03_02: Back to CC set speed
Back to CC at previous
